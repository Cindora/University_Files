;; Построение семейства из 14 ромбов с общей вершиной
;; Начальная точка P1 = (500, 220), шаг поворота 0.02*PI
;; Длина стороны запрашивается у пользователя.

(DEFUN C:LR8 ()
  ; 1. Задаём начальную точку (фиксирована по варианту)
  (SETQ P1 (LIST 500 220))
  
  ; 2. Запрашиваем длину стороны ромба
  (SETQ L (GETDIST P1 "\nВведите длину стороны ромба: "))
  
  ; 3. Угол ромба (60 градусов = PI/3), чтобы ромб не был квадратом
  (SETQ alpha (/ PI 3))
  
  ; 4. Шаг поворота (из задания)
  (SETQ step (* 0.02 PI))
  
  ; 5. Количество фигур (из задания)
  (SETQ N 14)
  
  ; 6. Счётчик цикла
  (SETQ i 0)
  
  ; 7. Цикл построения ромбов
  (WHILE (< i N)
    ; Угол поворота текущего ромба
    (SETQ B (* i step))
    
    ; Вычисляем вершины ромба относительно P1
    ; P1 - общая вершина (левый нижний угол)
    (SETQ P2 (POLAR P1 B L))                     ; соседняя вершина по одной стороне
    (SETQ P3 (POLAR P1 (+ B alpha) L))           ; соседняя вершина по другой стороне
    (SETQ P4 (POLAR P2 (+ B alpha) L))           ; противоположная вершина
    
    ; Строим ромб как замкнутую ломаную линию
    (COMMAND "LINE" P1 P2 P4 P3 "C")
    
    ; Увеличиваем счётчик
    (SETQ i (1+ i))
  )
  
  ; Выводим сообщение об успешном завершении
  (PRINC "\nПостроено 14 ромбов.")
  (PRINC)
)
