(DEFUN C:LR6 ()
  ; ------------------------------------------------------------
  ; 1. Задаём n и вычисляем координаты точек
  (SETQ n 67)

  ; Точка T1
  (SETQ T1 (LIST (+ 20 n) (+ 50 n)))   ; (87 117)

  ; Точка T2
  (SETQ T2 (LIST (- 80 n) (- 100 n)))  ; (13 33)

  ; Точка T3 по полярным координатам (R=33, угол=107°)
  (SETQ R_polar (- 100 n))              ; 33
  (SETQ angle_deg 107)
  (SETQ angle_rad (* angle_deg (/ PI 180.0)))
  (SETQ T3 (POLAR '(0 0) angle_rad R_polar))  ; вычисляем декартовы координаты

  ; ------------------------------------------------------------
  ; 2. Построение линии через T1, T2, T3 (ломаная)
  (COMMAND "LINE" T1 T2 T3 "")

  ; ------------------------------------------------------------
  ; 3. Окружность: центр и радиус
  (SETQ PC (LIST (- 100 n) (+ 100 n))) ; (33 167)
  (SETQ R_circ (+ 70 n))               ; 137
  (COMMAND "CIRCLE" PC R_circ)

  ; ------------------------------------------------------------
  ; 4. Вычисление K = A*B*C с заданными значениями (п.3)
  (SETQ A (+ 15 n))  ; 82
  (SETQ B (+ 5 n))   ; 72
  (SETQ C (+ 5 n))   ; 72
  (SETQ K (* A B C)) ; 425088

  ; ------------------------------------------------------------
  ; 5. Вывод на экран всех данных (п.5)
  (PRINC "\nРезультат:")
  (PRINC "\nЗадание 1: Точки для построения линии:")
  (PRINC "\n  T1 = ") (PRINC T1)
  (PRINC "\n  T2 = ") (PRINC T2)
  (PRINC "\n  T3 (полярные: R=33, угол=107°) = ") (PRINC T3)

  (PRINC "\n\nЗадание 2: Окружность:")
  (PRINC "\n  Центр PC = ") (PRINC PC)
  (PRINC "\n  Радиус R = ") (PRINC R_circ)

  (PRINC "\n\nЗадание 3: Вычисление K = A*B*C")
  (PRINC "\n  A = ") (PRINC A)
  (PRINC "\n  B = ") (PRINC B)
  (PRINC "\n  C = ") (PRINC C)
  (PRINC "\n  K = ") (PRINC K)

  ; ------------------------------------------------------------
  ; 6. Задание 4: ввод A, B, C с клавиатуры (GETINT)
  (PRINC "\n\nЗадание 4: Введите новые значения A, B, C (целые числа):")
  (SETQ A_in (GETINT "\nВведите A: "))
  (SETQ B_in (GETINT "Введите B: "))
  (SETQ C_in (GETINT "Введите C: "))
  (SETQ K_in (* A_in B_in C_in))
  (PRINC "\n  Введены: A = ") (PRINC A_in)
  (PRINC ", B = ") (PRINC B_in)
  (PRINC ", C = ") (PRINC C_in)
  (PRINC ", K = ") (PRINC K_in)

  (PRINC) ; завершаем без лишнего вывода
)
