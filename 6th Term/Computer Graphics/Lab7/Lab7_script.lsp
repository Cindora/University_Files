;; Построение окружности, вписанной в равнобедренный прямоугольный треугольник.
;; Параметры: центр окружности и радиус.

(DEFUN C:TRIANGLE ()
  ; 1. Запрашиваем центр окружности
  (SETQ PC (GETPOINT "\nУкажите центр окружности: "))
  
  ; 2. Запрашиваем радиус (с "резиновой" линией от центра)
  (SETQ R (GETDIST PC "\nВведите радиус окружности: "))
  
  ; 3. Строим окружность
  (COMMAND "CIRCLE" PC R)
  
  ; 4. Вычисляем вершины треугольника, описанного вокруг окружности.
  ;    Используем формулы для равнобедренного прямоугольного треугольника:
  ;    - Вершина прямого угла A находится на вертикали над центром на расстоянии R*sqrt(2)
  ;    - Основание BC горизонтально, на расстоянии R ниже центра,
  ;      полуширина основания = R*(1 + sqrt(2))
  (SETQ sqrt2 (SQRT 2.0))
  
  ; Вершина A (прямой угол, верхняя)
  (SETQ A (LIST (CAR PC) (+ (CADR PC) (* R sqrt2))))
  
  ; Вершина B (левая нижняя)
  (SETQ B (LIST (- (CAR PC) (* R (+ 1 sqrt2))) (- (CADR PC) R)))
  
  ; Вершина C (правая нижняя)
  (SETQ C (LIST (+ (CAR PC) (* R (+ 1 sqrt2))) (- (CADR PC) R)))
  
  ; 5. Строим треугольник (замкнутая ломаная)
  (COMMAND "LINE" A B C "C")
  
  ; 6. Выводим сообщение об успешном построении
  (PRINC "\nТреугольник построен.")
  (PRINC)
)
